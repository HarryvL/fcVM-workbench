# ***************************************************************************
# *                                                                         *
# *   Copyright (c) 2024 - Harry van Langen <hvlanalysis@gmail.com>        *
# *                                                                         *
# *   This program is free software; you can redistribute it and/or modify  *
# *   it under the terms of the GNU Lesser General Public License (LGPL)    *
# *   as published by the Free Software Foundation; either version 2 of     *
# *   the License, or (at your option) any later version.                   *
# *   for detail see the LICENCE text file.                                 *
# *                                                                         *
# *   This program is distributed in the hope that it will be useful,       *
# *   but WITHOUT ANY WARRANTY; without even the implied warranty of        *
# *   MERCHANTABILITY or FITNESS FOR A PARTICULAR PURPOSE.  See the         *
# *   GNU Library General Public License for more details.                  *
# *                                                                         *
# *   You should have received a copy of the GNU Library General Public     *
# *   License along with this program; if not, write to the Free Software   *
# *   Foundation, Inc., 59 Temple Place, Suite 330, Boston, MA  02111-1307  *
# *   USA                                                                   *
# *                                                                         *
# ***************************************************************************

import os
import sys
import time
import math
# import pstats
import dummyVM
# import cProfile
import FreeCAD as App
import FreeCADGui as Gui

print("fcVM.FCMacro")

mdir = os.path.dirname(dummyVM.file_path())
name = App.ActiveDocument.Label
file_path = os.path.join(mdir, "control files", name + '.inp')
macro_path = os.path.join(mdir, 'source code')

global progress_update

fcVM_window.progressBar.setValue(0)
fcVM_window.Step.setText("0")
fcVM_window.Load_Factor.setText("0.000")
fcVM_window.PEEQ.setText("0.000")
fcVM_window.CSR.setText("0.000")


def prn_upd(*args):
    for obj in args:
        print(str(obj), end='')
    print('\n')
    Gui.updateGui()


if 'fcVM' in sys.modules.keys():
    del (sys.modules['fcVM'])
    print("fcVM in sys.modules.keys")
else:
    sys.path.append(macro_path)
    print("fcVM path added")

import fcVM as ft

if 'fcVM' in sys.modules.keys():
    print("fcVM imported correctly")
else:
    print("fcVM not imported correctly")


t = 7 * [0.0]

try:
    with open(file_path, encoding='utf8') as f:
        sig_yield = float(f.readline().strip())
        grav_x = float(f.readline().strip())
        grav_y = float(f.readline().strip())
        grav_z = float(f.readline().strip())
        nstep = int(f.readline().strip())
        iterat_max = int(f.readline().strip())
        error_max = float(f.readline().strip())
        relax = float(f.readline().strip())
        scale_re = float(f.readline().strip())
        scale_up = float(f.readline().strip())
        scale_dn = float(f.readline().strip())
        disp_output = f.readline().strip()
        ultimate_strain = float(f.readline().strip())
        Et_E = float(f.readline().strip())
        target_LF = float(f.readline().strip())
        csr_option = f.readline().strip()
        averaged_option = f.readline().strip()
        gnl = f.readline().strip()
        maxImp = f.readline().strip()
        ev1 = f.readline().strip()
        ev2 = f.readline().strip()

except:
    print("file not found")

# extract information from FreeCAD objects
Gui.updateGui()
t0 = time.time()
doc, mesh, analysis, return_code = ft.setUpAnalysis()
t1 = time.time()
t[0] = t1 - t0
prn_upd(f"extract information from FreeCAD objects - time taken:  {t1 - t0:7.3f}  seconds\n")

if return_code == 1:
    prn_upd("No mesh object. Please create one first")
elif return_code == 2:
    prn_upd("No mesh. Please generate mesh first")
elif return_code == 3:
    prn_upd("No Analysis object. Please create one first")

if return_code == 0:
    # prepare finite element input
    prn_upd("prepare finite element input\n")
    t0 = time.time()
    (elNodes, noCoord, fix, fixdof, movdof, elMat, noce, loadFaces, pressure, loadvertices, vertexloads,
     loadedges, edgeloads, loadfaces_uni, faceloads) = ft.setUpInput(doc, mesh, analysis)

    t1 = time.time()
    t[1] = t1 - t0
    prn_upd(f"prepare finite element input - time taken:  {t1 - t0:7.3f}  seconds\n")

    # calculate the global stiffness matrix and global load vector
    prn_upd("calculate the GSM and GLV\n")
    t0 = time.time()
    stm, row, col, globalLoadVector, modf, V, loadsumx, loadsumy, loadsumz, ne, nn, x = ft.calcGSM(elNodes, noCoord,
                                                                                                   elMat,
                                                                                                   fix, grav_x, grav_y,
                                                                                                   grav_z,
                                                                                                   loadFaces, pressure,
                                                                                                   loadvertices,
                                                                                                   vertexloads,
                                                                                                   loadedges, edgeloads,
                                                                                                   loadfaces_uni,
                                                                                                   faceloads)

    t1 = time.time()
    t[2] = t1 - t0
    prn_upd(f"calculate the GSM and GLV - time taken:  {t1 - t0:7.3f}  seconds\n")

    # solve the global stiffness matrix equation
    prn_upd("solve the global stiffness matrix equation\n")
    Gui.updateGui()
    t0 = time.time()

    displacements, disp_el, eigenval, eigenvec, stresses, peeq, sigmises, csr, lout, un, crip, peeqplot, pplot, svmplot, triaxplot, ecrplot, csrplot, fail, nocoord_old = ft.calcDisp(
        elNodes, noCoord, fixdof, movdof, modf, elMat,
        stm, row, col, globalLoadVector, nstep, iterat_max,
        error_max, relax, scale_re, scale_up, scale_dn, sig_yield, disp_output,
        ultimate_strain, fcVM_window, Et_E, target_LF, x, noce, fix, grav_x, grav_y, grav_z, loadFaces, pressure,
        loadvertices, vertexloads, loadedges, edgeloads, loadfaces_uni, faceloads, gnl, maxImp, ev1, ev2)

    # pr = cProfile.runctx('displacements, disp_el, eigenval, eigenvec, stresses, peeq, sigmises, csr, lout, un, crip, peeqplot, pplot, svmplot, triaxplot, ecrplot, csrplot, fail, nocoord_old = ft.calcDisp(\
    #         elNodes, noCoord, fixdof, movdof, modf, elMat,\
    #         stm, row, col, globalLoadVector, nstep, iterat_max,\
    #         error_max, relax, scale_re, scale_up, scale_dn, sig_yield, disp_output,\
    #         ultimate_strain, fcVM_window, Et_E, target_LF, x, noce, fix, grav_x, grav_y, grav_z, loadFaces, pressure,\
    #         loadvertices, vertexloads, loadedges, edgeloads, loadfaces_uni, faceloads, gnl, maxImp, ev1, ev2)', globals(), locals(), filename="stats.prof")


    t1 = time.time()
    t[3] = t1 - t0
    prn_upd(f"solve the global stiffness matrix equation - time taken:  {t1 - t0:7.3f}  seconds\n")

    if not fail:
        # map stresses to nodal points
        prn_upd("map stresses and strains to nodal points\n")
        t0 = time.time()
        # averaged = fcVM_window.averagedChk.isChecked()
        averaged = False
        tet10stress, tet10peeq, tet10csr, tet10svm, tet10triax = ft.mapStresses(averaged, elNodes, noCoord, stresses,
                                                                                peeq, sigmises, csr, noce, sig_yield)
        t1 = time.time()
        t[4] = t1 - t0

        prn_upd(f"map stresses to nodal points - time taken:  {t1 - t0:7.3f}  seconds\n")

        # paste results in the FEM result object
        prn_upd("paste results in the FEM result object\n")
        t0 = time.time()
        resVol = ft.pasteResults(gnl, doc, elNodes, noCoord, nocoord_old, displacements, disp_el, eigenval, eigenvec, tet10stress,
                                 tet10peeq, tet10csr, tet10svm, maxImp, nstep)
        t1 = time.time()
        t[5] = t1 - t0
        prn_upd(f"paste results in the FEM result object - time taken:  {t1 - t0:7.3f}  seconds\n")

        # paste results in the FEM result object
        prn_upd("export results to VTK\n")
        t0 = time.time()
        VTKfile = os.path.join(mdir, "output files", name + '.vtk')
        ft.exportVTK(gnl, elNodes, noCoord, nocoord_old, displacements, disp_el, eigenval, eigenvec, tet10stress, tet10peeq,
                     tet10csr, tet10svm, tet10triax, sig_yield, VTKfile, maxImp, nstep)
        t1 = time.time()
        t[6] = t1 - t0
        prn_upd(f"export results to VTK - time taken:  {t1 - t0:7.3f}  seconds\n")

    timer = [f"extract information from FreeCAD objects....................... {t[0]:7.3f} seconds",
             f"prepare finite element input................................... {t[1]:7.3f} seconds",
             f"calculate the global stiffness matrix and global load vector... {t[2]:7.3f} seconds",
             f"solve the global stiffness matrix equation...................... {t[3]:7.3f} seconds",
             f"map stresses to nodal points................................... {t[4]:7.3f} seconds",
             f"paste results in the FEM result object......................... {t[5]:7.3f} seconds",
             f"export results to VTK.......................................... {t[6]:7.3f} seconds"]

    prn_upd("------------------------------ SUMMARY ------------------------------")
    for entry in timer:
        prn_upd(entry)

    file_path = os.path.join(mdir, "output files", name + '.out')

    with open(file_path, "w") as f:
        f.write("model name:{0: >50}\n".format(name))
        f.write("No. of elements:{0: >45}\n".format(ne))
        f.write("No. of Degrees of freedom:{0: >35}\n".format(nn))
        if gnl == "GNLY":
            if float(nstep) == 1.0:
                f.write("analysis type:{0: >47}\n".format("elastic buckling analysis"))
                f.write("elastic buckling factors:{0: >36}\n".format(str(eigenval)))
            else:
                f.write("analysis type:{0: >47}\n".format("elastic-plastic, geometric non-linear"))
                f.write("elastic buckling factors:{0: >36}\n".format(str(eigenval)))
        else:
            if float(nstep) == 1.0:
                f.write("analysis type: elastic\n")
            else:
                f.write("analysis type: elastic-plastic, geometric linear\n")

        f.write(
            "\n=========================================================================================================================\n\n")
        f.write("Sum of loads x-direction: {0: >15.2e}\n".format(loadsumx))
        f.write("Sum of loads y-direction: {0: >15.2e}\n".format(loadsumy))
        f.write("Sum of loads z-direction: {0: >15.2e}\n".format(loadsumz))
        f.write(
            "\n=========================================================================================================================\n\n")
        f.write(
            "{0: >8}{1: >10}{2: >10}{3: >10}{4: >10}{5: >10}{6: >10}{7: >10}{8: >10}{9: >10}{10: >10}{11: >10}\n".format(
                "Gauss point", "x", "y", "z", "load",
                "disp", "peeq", "pressure", "svmises",
                "triax", "eps_cr", "csr_max"))
        for i in range(len(crip)):
            f.write(
                '{0: 11d}{1: >10.2e}{2: >10.2e}{3: >10.2e}{4: >10.2e}{5: >10.2e}{6: >10.2e}{7: >10.2e}{8: >10.2e}{9: >10.2e}{10: >10.2e}{11: >10.2e}\n'.format(
                    crip[i], x[crip[i]][0], x[crip[i]][1], x[crip[i]][2], lout[i], un[i], peeqplot[i], pplot[i],
                    svmplot[i],
                    triaxplot[i], ecrplot[i], csrplot[i]))

        f.write(
            "\n=========================================================================================================================\n\n")

    f.close()

    fcVM_window.progressBar.setValue(0)
    fcVM_window.Step.setText("0")
    fcVM_window.Load_Factor.setText("0.000")
