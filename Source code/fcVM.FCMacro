# ***************************************************************************
# *                                                                         *
# *   Copyright (c) 2019 - Harry van Langen <hvlanalysis@icloud.com>        *
# *                                                                         *
# *   This program is free software; you can redistribute it and/or modify  *
# *   it under the terms of the GNU Lesser General Public License (LGPL)    *
# *   as published by the Free Software Foundation; either version 2 of     *
# *   the License, or (at your option) any later version.                   *
# *   for detail see the LICENCE text file.                                 *
# *                                                                         *
# *   This program is distributed in the hope that it will be useful,       *
# *   but WITHOUT ANY WARRANTY; without even the implied warranty of        *
# *   MERCHANTABILITY or FITNESS FOR A PARTICULAR PURPOSE.  See the         *
# *   GNU Library General Public License for more details.                  *
# *                                                                         *
# *   You should have received a copy of the GNU Library General Public     *
# *   License along with this program; if not, write to the Free Software   *
# *   Foundation, Inc., 59 Temple Place, Suite 330, Boston, MA  02111-1307  *
# *   USA                                                                   *
# *                                                                         *
# ***************************************************************************

import os
import sys
import time
import math
import FreeCAD as App
import FreeCADGui as Gui
import cProfile, pstats

profiler = cProfile.Profile()


def prn_upd(*args):
    for obj in args:
        print(str(obj), end='')
    print('\n')
    Gui.updateGui()


prn_upd("fcVM.FCMacro started")

if 'fcVM' in sys.modules.keys():
    del (sys.modules['fcVM'])
    prn_upd("fcVM in sys.modules.keys")
else:
    sys.path.append(App.getUserMacroDir(True))
    prn_upd("fcVM path added")

import fcVM as ft

t = 6 * [0.0]

mdir = App.getUserMacroDir(True)
name = App.ActiveDocument.Name
with open(mdir + '/../Control files/' + name + '.inp', encoding='utf8') as f:
    file_raw = f.readlines()

fc = []
for line in file_raw:
    list = (line.strip()).split()
    fc.append(list)

# material input values - TODO: merge with FEM WB input dialogues
gravity = float(fc[0][0])  # specific gravity acting in z-direction [N/mm3] = [1.0e+6 kN/m3]
sig_yield = float(fc[1][0])  # yield stress [MPa] for volume elements (von Mises material)
shr_yield = float(fc[2][0])  # yield stress [MPa] for interface elements (Cohesive material)
kn = float(fc[3][0])  # interface elastic normal stiffness factor (0.0 < kn <1.0)
ks = float(fc[4][0])  # interface elastic shear stiffness factor (0.0 < ks <1.0)

# control input values - TODO: merge with FEM WB input dialogues
out_disp = int(fc[5][
                   0])  # +n: output total discplacment at step n ; -n: output incremental discplacement at step n (if n>last step then n=last step)
nstep = int(fc[6][0])  # number of load steps per run (default = 10). nstep == 1: elastic analysis
iterat_max = float(fc[7][0])  # max number of iterations per step - this triggers a scale-down and restart
error_max = float(fc[8][0])  # convergence tolerance (default = 1.0e-03)
relax = float(fc[9][0])  # numerical over-relaxation (1.0 < relax < 1.5; default = 1.2)
scale_re = float(fc[10][0])  # scale factor for re-start (default = 2.0)
scale_up = float(fc[11][0])  # scale up for fast convergence (default = 1.2)
scale_dn = float(fc[12][0])  # scale down for slow convergence (default = 1.2)
phi = float(fc[13][0])  # friction angle
psi = float(fc[14][0])  # dilation angle
ts = float(fc[15][0])  # tensile strength [MPa]
mmod = float(fc[16][0])  # material model (1 = von Mises / Drucker Prager, 2 = Mohr Coulomb)

phi = math.radians(phi)
psi = math.radians(psi)

# extract information from FreeCAD objects
Gui.updateGui()
t0 = time.time()
doc, mesh, analysis = ft.setUpAnalysis()
t1 = time.time()
t[0] = t1 - t0
prn_upd(f"extract information from FreeCAD objects - time taken:  {t1 - t0:7.3f}  seconds\n")

# prepare finite element input
prn_upd("prepare finite element input\n")
t0 = time.time()
elNodes, noCoord, fix, fixdof, movdof, loadFaces, elMat, noce, pressure = ft.setUpInput(doc, mesh, analysis)

t1 = time.time()
t[1] = t1 - t0
prn_upd(f"prepare finite element input - time taken:  {t1 - t0:7.3f}  seconds\n")

# calculate the global stiffness matrix and global load vector
prn_upd("calculate the GSM and GLV\n")
t0 = time.time()
stm, row, col, globalLoadVector, modf = ft.calcGSM(elNodes, noCoord, elMat, fix, loadFaces, gravity, pressure)

t1 = time.time()
t[2] = t1 - t0
prn_upd(f"calculate the GSM and GLV - time taken:  {t1 - t0:7.3f}  seconds\n")

# solve the global stiffness matrix equation
prn_upd("solve the global stiffness matrix equation\n")
Gui.updateGui()
t0 = time.time()

profiler.enable()
displacements, stresses, peeq = ft.calcDisp(elNodes, noCoord, fixdof, movdof, modf, elMat,
                                            stm, row, col, globalLoadVector, nstep, iterat_max,
                                            error_max, relax, scale_re, scale_up, scale_dn, sig_yield, out_disp)
profiler.disable()
stats = pstats.Stats(profiler).sort_stats('cumtime')
stats.dump_stats('/home/harryvl/calcDISP_stats.dat')

t1 = time.time()
t[3] = t1 - t0
prn_upd(f"solve the global stiffness matrix equation - time taken:  {t1 - t0:7.3f}  seconds\n")

# map stresses to nodal points
prn_upd("map stresses and strains to nodal points\n")
t0 = time.time()
tet10stress, tet10peeq = ft.mapStresses(elNodes, noCoord, stresses, peeq, noce)
t1 = time.time()
t[4] = t1 - t0

prn_upd(f"map stresses to nodal points - time taken:  {t1 - t0:7.3f}  seconds\n")

# paste results in the FEM result object
prn_upd("paste results in the FEM result object\n")
t0 = time.time()
resVol = ft.pasteResults(doc, elNodes, noCoord, displacements, tet10stress, tet10peeq)
t1 = time.time()
t[5] = t1 - t0
prn_upd(f"paste results in the FEM result object - time taken:  {t1 - t0:7.3f}  seconds\n")

timer = [f"extract information from FreeCAD objects....................... {t[0]:7.3f} seconds",
         f"prepare finite element input................................... {t[1]:7.3f} seconds",
         f"calculate the global stiffness matrix and global load vector... {t[2]:7.3f} seconds",
         f"solve the global siffness matrix equation...................... {t[3]:7.3f} seconds",
         f"map stresses to nodal points................................... {t[4]:7.3f} seconds",
         f"paste results in the FEM result object......................... {t[5]:7.3f} seconds"]

prn_upd("------------------------------ SUMMARY ------------------------------")
for entry in timer:
    prn_upd(entry)
